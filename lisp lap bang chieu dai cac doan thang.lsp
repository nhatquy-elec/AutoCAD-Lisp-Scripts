;-----------------Lap bang chieu dai cac doan thang ----------------------------
; Free lisp code from CADViet - edit by Mathan
(defun C:LBCD (/ tot_len ss e_name e_record e_type TX TY kcach)
(setq diem (getpoint "\Chon vi tri ghi chieu dai cac doan... "))
(setq kcach (getreal "\Khoang cach cac text trong bang... "))
(prompt "\nChon cac doan can tinh chieu lap bang chieu dai: ")
(setq ss (ssget))
(setq sdt 0)
(if (null ss)
(exit)
)

(while (> (sslength ss) 0)
(setq e_name (ssname ss 0))
(setq e_record (entget e_name))
(setq e_type (cdr (assoc '0 e_record)))
(cond ((wcmatch e_type "LINE,ARC,CIRCLE,POLYLINE,LWPOLYLINE,ELLIPSE,SPLINE")
(command "lengthen" e_name "")
(setq tot_len (getvar "PERIMETER"))
(setq vitri ( + 1 sdt))
(setq diem1 (list (car diem) (- (cadr diem)( * sdt kcach))))
(setq diem2 (list (+ (* 2 kcach) (car diem)) (- (cadr diem) ( * sdt kcach))))
(setq chu1 (strcat "\ " (rtos vitri 2 0)))
(setq chu2 (strcat "\ " (rtos tot_len 2 3)))
(command "TEXT" diem1 "" "" chu1)
(command "TEXT" diem2 "" "" chu2)
(ssdel e_name ss)
(setq sdt (1+ sdt))
)
((wcmatch e_type "MLINE") (add_mline))
(e_type (ssdel e_name ss))
)
)

(princ)
)
