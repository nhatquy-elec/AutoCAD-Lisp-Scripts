;; (doi tuong trong lisp phai la: polyline, dtext)
;; free lisp from cadviet.com
;;; this lisp was downloaded from http://www.cadviet.com/forum/topic/47335-da-xong-lisp-xuat-chieu-dai-line-ra-text-co-san-va-co-tien-to-hau-to/
(defun c:cc (/ doituong total dtuong1 tdt dt ktext ktratext ktratext1 ktextcu textdt ktextmoi newcolor oldcolor)
   (setq doituong (ssget '((0 . "*POLYLINE"))))
   (setq total (sslength doituong))
   (setq tdt 0)
   (repeat total
         (setq total (- total 1))
         (setq dtuong1 (cdr (car (entget (ssname doituong total)))))
         (command "area" "e" dtuong1)
         (setq dt (getvar "Perimeter"))
         (setq tdt (+ tdt dt))
   )
   (setq ktext (car (entsel "chon vao text can ghi: ")))
   (setq ktratext (entget ktext))
   (setq ktratext1 (cdr (assoc 0 ktratext)))
   (if (= ktratext1 "TEXT")
       (progn
               (setq ktextcu (assoc 1 ktratext))
               (setq textdt (strcat "L= " (rtos (- tdt 0) 2 2) " m"))
               (setq ktextmoi (cons 1 textdt))
               (setq ktratext (subst ktextmoi ktextcu ktratext))
               (entmod ktratext)
               (setq color 4)
               (setq newcolor (cons 62 color))
                  (if (assoc 62 ktratext)
                      (progn
                           (setq oldcolor (assoc 62 ktratext))
                           (setq ktratext (subst newcolor oldcolor ktratext))
                           (entmod ktratext)
                      )
                      (entmod (append ktratext (list (cons 62 color))))
                   )
        )
        (alert "Chon doi tuong la text!")
   )
  (textpage)
  (graphscr)
)
